Option Explicit On
Imports Inventor
Imports System
Imports System.Collections.Generic

Sub Main()
    Dim app As Inventor.Application = ThisApplication
    Dim doc As DrawingDocument = TryCast(app.ActiveDocument, DrawingDocument)

    If doc Is Nothing Then
        System.Windows.Forms.MessageBox.Show("Откройте документ чертежа (.idw или .dwg).", "Извлечение аннотаций")
        Return
    End If

    Dim processed As Integer = 0
    Dim skipped As Integer = 0
    Dim arranged As Integer = 0
    Dim clamped As Integer = 0
    Dim overlapResolved As Integer = 0
    Dim commandRuns As Integer = 0

    ' Проходим по всем листам в документе
    For Each sh As Sheet In doc.Sheets
        ' Проходим по всем видам на текущем листе
        For Each v As DrawingView In sh.DrawingViews
            Try
                ' 1. Извлечение размеров/аннотаций через API + (по возможности) команды Inventor.
                commandRuns += RetrieveForViewWithFallback(doc, sh, v, app)

                processed += 1
            Catch
                skipped += 1
            End Try
        Next

        ' 3. Упорядочиваем размеры на листе (группируем по ориентации и применяем Arrange)
        arranged += ArrangeDimensionsOnSheet(sh, app)

        ' 4. Ограничиваем положение размеров рамками листа
        clamped += ClampDimensionsToSheetBounds(sh, app)

        ' 5. Разводим размеры, чтобы они не накладывались друг на друга
        overlapResolved += ResolveDimensionOverlaps(sh, app)

        ' 6. Финальная "жесткая" проверка — ни один размер не должен остаться за рамкой.
        clamped += EnforceBoundsHard(sh, app)
    Next

    ' Обновляем чертеж для отображения изменений
    doc.Update2(True)

    System.Windows.Forms.MessageBox.Show("Обработано видов: " & processed.ToString() & vbCrLf &
                                         "Пропущено: " & skipped.ToString() & vbCrLf &
                                         "Упорядочено размеров: " & arranged.ToString() & vbCrLf &
                                         "Возвращено в границы листа: " & clamped.ToString() & vbCrLf &
                                         "Разведено пересечений: " & overlapResolved.ToString() & vbCrLf &
                                         "Запусков команд Inventor: " & commandRuns.ToString(), "Готово")
End Sub

Private Function RetrieveForViewWithFallback(doc As DrawingDocument,
                                             sh As Sheet,
                                             v As DrawingView,
                                             app As Inventor.Application) As Integer
    If doc Is Nothing OrElse sh Is Nothing OrElse v Is Nothing OrElse app Is Nothing Then Return 0

    Dim commandRuns As Integer = 0

    ' A) Базовый путь: Retrieve через API (наиболее стабильный).
    Try
        sh.DrawingDimensions.GeneralDimensions.Retrieve(v)
    Catch
    End Try

    ' B) PMI/3D-аннотации.
    Try
        v.Include3DAnnotations = True
    Catch
    End Try

    ' C) Fallback: пробуем встроенные команды Inventor.
    ' Команды могут отличаться между версиями/локалями, поэтому перебираем набор известных InternalName.
    Dim retrieveCmdNames As String() = {
        "DrawingRetrieveDimensionsCmd",
        "DrawingRetrieveDimsCmd",
        "DrawingGetModelAnnotationsCmd",
        "DrawingRetrieveModelAnnotationsCmd"
    }

    Try
        doc.Activate()
    Catch
    End Try

    For Each cmdName As String In retrieveCmdNames
        Try
            Dim cmd As ControlDefinition = app.CommandManager.ControlDefinitions.Item(cmdName)
            If cmd Is Nothing Then Continue For

            Try
                doc.SelectSet.Clear()
                doc.SelectSet.Select(v)
            Catch
            End Try

            Try
                cmd.Execute2(True)
            Catch
                cmd.Execute()
            End Try

            commandRuns += 1
        Catch
            ' В конкретной версии команды может не быть — это ожидаемо.
        End Try
    Next

    Return commandRuns
End Function

Private Function ArrangeDimensionsOnSheet(sh As Sheet, app As Inventor.Application) As Integer
    If sh Is Nothing OrElse app Is Nothing Then Return 0

    Dim horizontal As New List(Of GeneralDimension)()
    Dim vertical As New List(Of GeneralDimension)()
    Dim angled As New List(Of GeneralDimension)()

    For Each gd As GeneralDimension In sh.DrawingDimensions.GeneralDimensions
        If gd Is Nothing Then Continue For

        ' Базовый шаг: текст в центр, чтобы после Arrange подписи выглядели ровнее.
        Try
            gd.CenterText()
        Catch
        End Try

        Dim bucket As Integer = GetDimensionBucket(gd)
        Select Case bucket
            Case 0
                horizontal.Add(gd)
            Case 1
                vertical.Add(gd)
            Case Else
                angled.Add(gd)
        End Select
    Next

    Dim arrangedCount As Integer = 0
    arrangedCount += ArrangeBucket(sh, app, horizontal)
    arrangedCount += ArrangeBucket(sh, app, vertical)
    arrangedCount += ArrangeBucket(sh, app, angled)

    Return arrangedCount
End Function

Private Function ClampDimensionsToSheetBounds(sh As Sheet, app As Inventor.Application) As Integer
    If sh Is Nothing OrElse app Is Nothing Then Return 0

    Dim moved As Integer = 0
    Dim tg As TransientGeometry = app.TransientGeometry
    If tg Is Nothing Then Return 0

    ' Небольшой отступ от кромок листа, чтобы текст не "прилипал" к границе.
    Dim margin As Double = 1.0
    Dim minX As Double = margin
    Dim minY As Double = margin
    Dim maxX As Double = Math.Max(minX, sh.Width - margin)
    Dim maxY As Double = Math.Max(minY, sh.Height - margin)

    For Each gd As GeneralDimension In sh.DrawingDimensions.GeneralDimensions
        If gd Is Nothing Then Continue For

        Try
            Dim x As Double = gd.Text.Origin.X
            Dim y As Double = gd.Text.Origin.Y
            Dim shiftX As Double = 0.0
            Dim shiftY As Double = 0.0

            ' Пытаемся удержать в пределах листа весь размер (по RangeBox).
            ' Если получить RangeBox не удалось, используем запасной вариант:
            ' ограничиваем только позицию текста размера.
            Dim rb As Box2d = GetDimensionRangeBox(gd)
            If rb IsNot Nothing Then
                If rb.MinPoint.X < minX Then shiftX = minX - rb.MinPoint.X
                If rb.MaxPoint.X > maxX Then shiftX = maxX - rb.MaxPoint.X
                If rb.MinPoint.Y < minY Then shiftY = minY - rb.MinPoint.Y
                If rb.MaxPoint.Y > maxY Then shiftY = maxY - rb.MaxPoint.Y
            Else
                Dim clampedX As Double = x
                Dim clampedY As Double = y
                If clampedX < minX Then clampedX = minX
                If clampedX > maxX Then clampedX = maxX
                If clampedY < minY Then clampedY = minY
                If clampedY > maxY Then clampedY = maxY
                shiftX = clampedX - x
                shiftY = clampedY - y
            End If

            If Math.Abs(shiftX) > 0.000001 OrElse Math.Abs(shiftY) > 0.000001 Then
                gd.Text.Origin = tg.CreatePoint2d(x + shiftX, y + shiftY)
                moved += 1
            End If
        Catch
            ' Не все типы размеров/состояния позволяют перемещать текст.
        End Try
    Next

    Return moved
End Function

Private Function ResolveDimensionOverlaps(sh As Sheet, app As Inventor.Application) As Integer
    If sh Is Nothing OrElse app Is Nothing Then Return 0

    Dim moved As Integer = 0
    Dim maxPasses As Integer = 6
    Dim tg As TransientGeometry = app.TransientGeometry
    If tg Is Nothing Then Return 0

    ' Ограничения "рабочей рамки" листа.
    Dim margin As Double = 1.0
    Dim minX As Double = margin
    Dim minY As Double = margin
    Dim maxX As Double = Math.Max(minX, sh.Width - margin)
    Dim maxY As Double = Math.Max(minY, sh.Height - margin)

    Dim dims As New List(Of GeneralDimension)()
    For Each gd As GeneralDimension In sh.DrawingDimensions.GeneralDimensions
        If gd IsNot Nothing Then dims.Add(gd)
    Next
    If dims.Count < 2 Then Return 0

    ' Стабильный порядок для читаемого результата.
    dims.Sort(AddressOf CompareDimensionsByTextOrigin)

    For pass As Integer = 1 To maxPasses
        Dim changedOnPass As Boolean = False

        For i As Integer = 0 To dims.Count - 1
            Dim a As GeneralDimension = dims(i)
            Dim rbA As Box2d = GetDimensionRangeBox(a)
            If rbA Is Nothing Then Continue For

            For j As Integer = i + 1 To dims.Count - 1
                Dim b As GeneralDimension = dims(j)
                Dim rbB As Box2d = GetDimensionRangeBox(b)
                If rbB Is Nothing Then Continue For

                If Not BoxesOverlap(rbA, rbB) Then Continue For

                Try
                    Dim orientation As Integer = GetDimensionBucket(b)
                    Dim x As Double = b.Text.Origin.X
                    Dim y As Double = b.Text.Origin.Y
                    Dim newX As Double = x
                    Dim newY As Double = y
                    Dim spacing As Double = 0.8

                    ' Разводим в направлении, наиболее типичном для ориентации размера:
                    ' горизонтальные — по Y, вертикальные — по X, прочие — диагональю.
                    Select Case orientation
                        Case 0
                            newY = y - (rbA.MaxPoint.Y - rbB.MinPoint.Y) - spacing
                        Case 1
                            newX = x + (rbA.MaxPoint.X - rbB.MinPoint.X) + spacing
                        Case Else
                            newX = x + spacing
                            newY = y - spacing
                    End Select

                    ' Гарантированно оставляем в пределах рамки листа.
                    newX = ClampValue(newX, minX, maxX)
                    newY = ClampValue(newY, minY, maxY)

                    If Math.Abs(newX - x) > 0.000001 OrElse Math.Abs(newY - y) > 0.000001 Then
                        b.Text.Origin = tg.CreatePoint2d(newX, newY)
                        moved += 1
                        changedOnPass = True
                        rbB = GetDimensionRangeBox(b)
                        If rbB Is Nothing Then Exit For
                    End If
                Catch
                    ' Некоторые размеры могут запрещать ручное смещение текста.
                End Try
            Next
        Next

        If Not changedOnPass Then Exit For
    Next

    ' После разведения повторно прижимаем к рамке для гарантии.
    moved += ClampDimensionsToSheetBounds(sh, app)
    Return moved
End Function

Private Function EnforceBoundsHard(sh As Sheet, app As Inventor.Application) As Integer
    If sh Is Nothing OrElse app Is Nothing Then Return 0

    Dim totalMoved As Integer = 0
    Dim maxPasses As Integer = 4
    For pass As Integer = 1 To maxPasses
        Dim movedOnPass As Integer = ClampDimensionsToSheetBounds(sh, app)
        totalMoved += movedOnPass
        If movedOnPass = 0 Then Exit For
    Next

    Return totalMoved
End Function

Private Function GetDimensionRangeBox(gd As GeneralDimension) As Box2d
    If gd Is Nothing Then Return Nothing

    Try
        Return gd.RangeBox
    Catch
        Return Nothing
    End Try
End Function

' 0 = горизонтальные, 1 = вертикальные, 2 = прочие/наклонные
Private Function GetDimensionBucket(gd As GeneralDimension) As Integer
    Try
        Dim ld As LinearGeneralDimension = TryCast(gd, LinearGeneralDimension)
        If ld IsNot Nothing Then
            Select Case ld.DimensionType
                Case DimensionTypeEnum.kHorizontalDimensionType
                    Return 0
                Case DimensionTypeEnum.kVerticalDimensionType
                    Return 1
                Case Else
                    Return 2
            End Select
        End If
    Catch
    End Try

    Return 2
End Function

Private Function ArrangeBucket(sh As Sheet,
                               app As Inventor.Application,
                               dims As List(Of GeneralDimension)) As Integer
    If sh Is Nothing OrElse app Is Nothing Then Return 0
    If dims Is Nothing OrElse dims.Count = 0 Then Return 0

    ' Сортируем, чтобы Arrange получал размеры в устойчивом порядке:
    ' сверху-вниз, затем слева-направо.
    dims.Sort(AddressOf CompareDimensionsByTextOrigin)

    Dim col As ObjectCollection = app.TransientObjects.CreateObjectCollection()
    For Each gd As GeneralDimension In dims
        col.Add(gd)
    Next

    Try
        sh.DrawingDimensions.Arrange(col)
        Return dims.Count
    Catch
        Return 0
    End Try
End Function

Private Function CompareDimensionsByTextOrigin(a As GeneralDimension,
                                               b As GeneralDimension) As Integer
    Dim ay As Double = 0.0
    Dim ax As Double = 0.0
    Dim by As Double = 0.0
    Dim bx As Double = 0.0

    Try
        ay = a.Text.Origin.Y
        ax = a.Text.Origin.X
    Catch
    End Try

    Try
        by = b.Text.Origin.Y
        bx = b.Text.Origin.X
    Catch
    End Try

    ' В системе координат листа обычно Y растет вверх.
    ' Для удобства чтения сортируем с верхней части к нижней.
    If ay > by Then Return -1
    If ay < by Then Return 1

    If ax < bx Then Return -1
    If ax > bx Then Return 1

    Return 0
End Function

Private Function BoxesOverlap(a As Box2d, b As Box2d) As Boolean
    If a Is Nothing OrElse b Is Nothing Then Return False

    If a.MaxPoint.X <= b.MinPoint.X Then Return False
    If b.MaxPoint.X <= a.MinPoint.X Then Return False
    If a.MaxPoint.Y <= b.MinPoint.Y Then Return False
    If b.MaxPoint.Y <= a.MinPoint.Y Then Return False

    Return True
End Function

Private Function ClampValue(value As Double, minValue As Double, maxValue As Double) As Double
    If value < minValue Then Return minValue
    If value > maxValue Then Return maxValue
    Return value
End Function
